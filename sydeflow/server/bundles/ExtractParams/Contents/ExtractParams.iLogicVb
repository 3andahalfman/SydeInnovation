' =====================================================
' PARAMETER EXTRACTION iLogic CODE FOR DESIGN AUTOMATION
' =====================================================
' For use with Autodesk Design Automation API
' Extracts all user parameters from Inventor IPT/IAM files
' and outputs them as JSON for SydeFlow Product Pipeline
' =====================================================

Imports System.IO
Imports Newtonsoft.Json

Sub Main()
    Try
        ' Get the active document
        Dim doc As Document = ThisApplication.ActiveDocument
        
        If doc Is Nothing Then
            LogError("No active document found")
            Exit Sub
        End If
        
        ' Create parameter list
        Dim paramList As New List(Of Object)
        
        ' Handle Part documents
        If TypeOf doc Is PartDocument Then
            Dim partDoc As PartDocument = doc
            ExtractUserParameters(partDoc.ComponentDefinition.Parameters.UserParameters, paramList)
            ExtractModelParameters(partDoc.ComponentDefinition.Parameters.ModelParameters, paramList)
        
        ' Handle Assembly documents
        ElseIf TypeOf doc Is AssemblyDocument Then
            Dim assyDoc As AssemblyDocument = doc
            ExtractUserParameters(assyDoc.ComponentDefinition.Parameters.UserParameters, paramList)
            ExtractModelParameters(assyDoc.ComponentDefinition.Parameters.ModelParameters, paramList)
        End If
        
        ' Create output object with metadata
        Dim output As New Dictionary(Of String, Object)
        output("fileName") = doc.DisplayName
        output("fullFileName") = doc.FullFileName
        output("fileType") = GetFileType(doc)
        output("documentType") = doc.DocumentType.ToString()
        output("parameters") = paramList
        output("extractedAt") = DateTime.UtcNow.ToString("o")
        output("parameterCount") = paramList.Count
        output("extractionVersion") = "2.0"
        output("source") = "DesignAutomation"
        
        ' Add document units info
        Try
            Dim units As UnitsOfMeasure = doc.UnitsOfMeasure
            output("documentUnits") = New Dictionary(Of String, Object) From {
                {"lengthUnits", GetLengthUnitString(units.LengthUnits)},
                {"angleUnits", GetAngleUnitString(units.AngleUnits)}
            }
        Catch
            ' Units not available
        End Try
        
        ' Serialize to JSON with formatting
        Dim settings As New JsonSerializerSettings()
        settings.Formatting = Formatting.Indented
        settings.NullValueHandling = NullValueHandling.Ignore
        Dim json As String = JsonConvert.SerializeObject(output, settings)
        
        ' Get output path - Design Automation sets working directory
        Dim outputPath As String = IO.Path.Combine(
            IO.Path.GetDirectoryName(doc.FullFileName), 
            "parameters.json"
        )
        
        ' Also try environment variable
        Dim envPath As String = Environment.GetEnvironmentVariable("DA_OUTPUT_JSON")
        If Not String.IsNullOrEmpty(envPath) Then
            outputPath = envPath
        End If
        
        ' Write to output file
        IO.File.WriteAllText(outputPath, json)
        
        ' Log success
        Logger.Info("✅ Parameters extracted successfully: " & paramList.Count & " parameters")
        Logger.Info("📄 Output written to: " & outputPath)
        
    Catch ex As Exception
        LogError("Extraction failed: " & ex.Message)
    End Try
End Sub

Sub ExtractUserParameters(userParams As UserParameters, paramList As List(Of Object))
    For Each param As UserParameter In userParams
        Try
            Dim paramInfo As New Dictionary(Of String, Object)
            
            ' Basic properties
            paramInfo("name") = param.Name
            paramInfo("displayName") = FormatDisplayName(param.Name)
            paramInfo("expression") = param.Expression
            paramInfo("unit") = GetUnitString(param)
            paramInfo("parameterSource") = "User"
            paramInfo("isKey") = False ' User can mark as key later
            
            ' Determine type and get value
            If param.ParameterType = ParameterTypeEnum.kTextParameter Then
                paramInfo("type") = "text"
                paramInfo("defaultValue") = param.Expression
                paramInfo("controlType") = "text"
            ElseIf param.ParameterType = ParameterTypeEnum.kBooleanParameter Then
                paramInfo("type") = "boolean"
                paramInfo("defaultValue") = param.Value
                paramInfo("controlType") = "checkbox"
            Else
                paramInfo("type") = "number"
                ' Get numeric value
                paramInfo("defaultValue") = Math.Round(param.Value, 4)
                paramInfo("controlType") = "slider"
                
                ' Try to get numeric limits if defined
                Try
                    If param.HasLimits Then
                        paramInfo("min") = Math.Round(param.LowerBound, 4)
                        paramInfo("max") = Math.Round(param.UpperBound, 4)
                    Else
                        ' Set sensible defaults based on current value
                        Dim currentVal As Double = param.Value
                        If currentVal > 0 Then
                            paramInfo("min") = Math.Round(currentVal * 0.1, 4)
                            paramInfo("max") = Math.Round(currentVal * 3, 4)
                        Else
                            paramInfo("min") = -1000
                            paramInfo("max") = 1000
                        End If
                    End If
                    paramInfo("step") = CalculateStep(paramInfo("min"), paramInfo("max"))
                Catch
                    ' Limits not available - use defaults
                    paramInfo("min") = 0
                    paramInfo("max") = 1000
                    paramInfo("step") = 1
                End Try
            End If
            
            ' Detect parameter group from name patterns
            paramInfo("group") = DetectGroup(param.Name, param.Units)
            
            ' Check if parameter name suggests it should be exposed
            paramInfo("exposed") = ShouldExposeParameter(param.Name)
            
            ' Add validation info
            paramInfo("required") = True
            
            ' Add to list
            paramList.Add(paramInfo)
            
        Catch ex As Exception
            Logger.Warn("Could not extract parameter: " & param.Name & " - " & ex.Message)
        End Try
    Next
End Sub

Sub ExtractModelParameters(modelParams As ModelParameters, paramList As List(Of Object))
    ' Extract key model parameters that might be useful
    ' Only include if they appear to be "dimension" type parameters
    For Each param As ModelParameter In modelParams
        Try
            ' Skip internal/system parameters
            If param.Name.StartsWith("d") AndAlso IsNumeric(param.Name.Substring(1)) Then
                ' This is a default dimension parameter (d0, d1, etc) - skip unless named
                Continue For
            End If
            
            ' Skip if already exists (from user parameters)
            Dim exists As Boolean = False
            For Each existing In paramList
                Dim existingDict = DirectCast(existing, Dictionary(Of String, Object))
                If existingDict("name").ToString() = param.Name Then
                    exists = True
                    Exit For
                End If
            Next
            
            If exists Then Continue For
            
            Dim paramInfo As New Dictionary(Of String, Object)
            paramInfo("name") = param.Name
            paramInfo("displayName") = FormatDisplayName(param.Name)
            paramInfo("expression") = param.Expression
            paramInfo("unit") = GetModelParamUnitString(param)
            paramInfo("type") = "number"
            paramInfo("defaultValue") = Math.Round(param.Value, 4)
            paramInfo("controlType") = "slider"
            paramInfo("parameterSource") = "Model"
            paramInfo("group") = DetectGroup(param.Name, param.Units)
            paramInfo("exposed") = False ' Model params not exposed by default
            paramInfo("isKey") = False
            
            ' Set range
            paramInfo("min") = Math.Round(param.Value * 0.1, 4)
            paramInfo("max") = Math.Round(param.Value * 3, 4)
            paramInfo("step") = CalculateStep(paramInfo("min"), paramInfo("max"))
            
            paramList.Add(paramInfo)
            
        Catch ex As Exception
            ' Skip this parameter
        End Try
    Next
End Sub

Function FormatDisplayName(name As String) As String
    ' Convert camelCase, PascalCase, snake_case to readable format
    Dim result As String = name
    
    ' Handle d0, d1, d2 style parameters
    If System.Text.RegularExpressions.Regex.IsMatch(name, "^d\d+$") Then
        Return "Dimension " & name.Substring(1)
    End If
    
    ' Handle underscore_case
    result = result.Replace("_", " ")
    
    ' Add spaces before capitals (camelCase/PascalCase)
    result = System.Text.RegularExpressions.Regex.Replace(result, "([a-z])([A-Z])", "$1 $2")
    
    ' Handle common abbreviations
    result = result.Replace(" Mm", " (mm)")
    result = result.Replace(" Cm", " (cm)")
    result = result.Replace(" In", " (in)")
    
    ' Capitalize first letter of each word
    result = System.Globalization.CultureInfo.CurrentCulture.TextInfo.ToTitleCase(result.ToLower())
    
    Return result.Trim()
End Function

Function GetUnitString(param As UserParameter) As String
    Try
        Dim unitType As UnitsTypeEnum = param.Units
        Return ConvertUnitsToString(unitType)
    Catch
        Return ""
    End Try
End Function

Function GetModelParamUnitString(param As ModelParameter) As String
    Try
        Dim unitType As UnitsTypeEnum = param.Units
        Return ConvertUnitsToString(unitType)
    Catch
        Return ""
    End Try
End Function

Function ConvertUnitsToString(unitType As UnitsTypeEnum) As String
    Select Case unitType
        Case UnitsTypeEnum.kMillimeterLengthUnits
            Return "mm"
        Case UnitsTypeEnum.kCentimeterLengthUnits
            Return "cm"
        Case UnitsTypeEnum.kMeterLengthUnits
            Return "m"
        Case UnitsTypeEnum.kInchLengthUnits
            Return "in"
        Case UnitsTypeEnum.kFootLengthUnits
            Return "ft"
        Case UnitsTypeEnum.kDegreeAngleUnits
            Return "deg"
        Case UnitsTypeEnum.kRadianAngleUnits
            Return "rad"
        Case UnitsTypeEnum.kKilogramMassUnits
            Return "kg"
        Case UnitsTypeEnum.kGramMassUnits
            Return "g"
        Case UnitsTypeEnum.kPoundMassUnits
            Return "lb"
        Case UnitsTypeEnum.kUnitlessUnits
            Return ""
        Case Else
            Return ""
    End Select
End Function

Function GetLengthUnitString(unitType As UnitsTypeEnum) As String
    Select Case unitType
        Case UnitsTypeEnum.kMillimeterLengthUnits
            Return "mm"
        Case UnitsTypeEnum.kCentimeterLengthUnits
            Return "cm"
        Case UnitsTypeEnum.kMeterLengthUnits
            Return "m"
        Case UnitsTypeEnum.kInchLengthUnits
            Return "in"
        Case UnitsTypeEnum.kFootLengthUnits
            Return "ft"
        Case Else
            Return "mm"
    End Select
End Function

Function GetAngleUnitString(unitType As UnitsTypeEnum) As String
    Select Case unitType
        Case UnitsTypeEnum.kDegreeAngleUnits
            Return "deg"
        Case UnitsTypeEnum.kRadianAngleUnits
            Return "rad"
        Case Else
            Return "deg"
    End Select
End Function

Function DetectGroup(name As String, unitType As UnitsTypeEnum) As String
    Dim nameLower As String = name.ToLower()
    
    ' Check name patterns first
    If nameLower.Contains("width") Or nameLower.Contains("depth") Or _
       nameLower.Contains("height") Or nameLower.Contains("length") Or _
       nameLower.Contains("size") Or nameLower.Contains("thick") Then
        Return "Dimensions"
    End If
    
    If nameLower.Contains("material") Or nameLower.Contains("finish") Or _
       nameLower.Contains("color") Or nameLower.Contains("texture") Or _
       nameLower.Contains("surface") Then
        Return "Material"
    End If
    
    If nameLower.Contains("angle") Or nameLower.Contains("rotation") Or _
       nameLower.Contains("tilt") Or nameLower.Contains("slope") Then
        Return "Angles"
    End If
    
    If nameLower.Contains("count") Or nameLower.Contains("qty") Or _
       nameLower.Contains("number") Or nameLower.Contains("quantity") Or _
       nameLower.Contains("num") Then
        Return "Quantity"
    End If
    
    If nameLower.Contains("radius") Or nameLower.Contains("fillet") Or _
       nameLower.Contains("chamfer") Or nameLower.Contains("round") Then
        Return "Features"
    End If
    
    If nameLower.Contains("hole") Or nameLower.Contains("bore") Or _
       nameLower.Contains("slot") Or nameLower.Contains("pocket") Then
        Return "Holes & Cuts"
    End If
    
    If nameLower.Contains("offset") Or nameLower.Contains("spacing") Or _
       nameLower.Contains("gap") Or nameLower.Contains("margin") Then
        Return "Spacing"
    End If
    
    ' Check unit type
    Select Case unitType
        Case UnitsTypeEnum.kMillimeterLengthUnits, _
             UnitsTypeEnum.kCentimeterLengthUnits, _
             UnitsTypeEnum.kMeterLengthUnits, _
             UnitsTypeEnum.kInchLengthUnits, _
             UnitsTypeEnum.kFootLengthUnits
            Return "Dimensions"
        Case UnitsTypeEnum.kDegreeAngleUnits, _
             UnitsTypeEnum.kRadianAngleUnits
            Return "Angles"
        Case Else
            Return "General"
    End Select
End Function

Function ShouldExposeParameter(name As String) As Boolean
    Dim nameLower As String = name.ToLower()
    
    ' Common user-facing parameter names
    Dim exposePatterns As String() = {
        "width", "height", "depth", "length", "size",
        "thick", "radius", "angle", "count", "qty",
        "material", "color", "finish", "type", "style"
    }
    
    For Each pattern In exposePatterns
        If nameLower.Contains(pattern) Then
            Return True
        End If
    Next
    
    ' Internal/technical parameter patterns to hide
    Dim hidePatterns As String() = {
        "_internal", "_calc", "_temp", "helper", "aux"
    }
    
    For Each pattern In hidePatterns
        If nameLower.Contains(pattern) Then
            Return False
        End If
    Next
    
    ' Default: expose user parameters
    Return True
End Function

Function CalculateStep(minVal As Object, maxVal As Object) As Double
    Try
        Dim range As Double = CDbl(maxVal) - CDbl(minVal)
        
        If range <= 1 Then
            Return 0.01
        ElseIf range <= 10 Then
            Return 0.1
        ElseIf range <= 100 Then
            Return 1
        ElseIf range <= 1000 Then
            Return 5
        Else
            Return 10
        End If
    Catch
        Return 1
    End Try
End Function

Function GetFileType(doc As Document) As String
    If TypeOf doc Is PartDocument Then
        Return "IPT"
    ElseIf TypeOf doc Is AssemblyDocument Then
        Return "IAM"
    ElseIf TypeOf doc Is DrawingDocument Then
        Return "IDW"
    ElseIf TypeOf doc Is PresentationDocument Then
        Return "IPN"
    Else
        Return "Unknown"
    End If
End Function

Sub LogError(message As String)
    Logger.Error("❌ " & message)
    
    ' Also write error to output file
    Try
        Dim errorOutput As New Dictionary(Of String, Object)
        errorOutput("success") = False
        errorOutput("error") = message
        errorOutput("extractedAt") = DateTime.UtcNow.ToString("o")
        
        Dim json As String = JsonConvert.SerializeObject(errorOutput, Formatting.Indented)
        IO.File.WriteAllText("parameters.json", json)
    Catch
        ' Can't write error file
    End Try
End Sub
